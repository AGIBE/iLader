FME workspace EsriGeodatabase2PostGIS.fmw

Parameters:
- INPUT_SDE =   # Input SDE-Connection-File
- POSTGIS_DB =   # Database
- POSTGIS_HOST =   # Host
- POSTGIS_PORT =   # Port
- POSTGIS_USER =   # Username
- POSTGIS_PASSWORD =   # Password
- LOGFILE =   # Logfile
- SCHEMA_NAME =   # Schemaname
- TABLE_HANDLING = DROP_CREATE
- TABELLEN =
- DATEFIELDS =   # " " Selected Attributes
- TABELLENTYP =

Writers:
- POSTGIS_1: POSTGIS to $(POSTGIS_DB)
- POSTGRES_1: POSTGRES to $(POSTGIS_DB)

Creator
    GEOMTYPE = Geometry Object
    NUM = 1
    CREATED -> FeatureReader [INITIATOR]
FeatureReader
    ATTR_ACCUM_MODE = Only Use Result
    COMBINE_GEOM = Use Result
    FEATURETYPES = $(TABELLEN)
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CLIP_TO_ENVELOPE = NO
    GEODATABASE_SDE_CONNECTION_FILE = $(INPUT_SDE)
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SEARCH_METHOD = GEODB_INTERSECTS
    GEODATABASE_SDE_SEARCH_ORDER = SPATIAL_FIRST
    GEODATABASE_SDE_SPLIT_COMPLEX_ANNOS = no
    GEODATABASE_SDE_SPLIT_COMPLEX_EDGES = no
    GEODATABASE_SDE_SPLIT_MULTI_PART_ANNOS = no
    GEODATABASE_SDE_TRANSLATE_SPATIAL_DATA_ONLY = no
    GEODATABASE_SDE_USE_SEARCH_ENVELOPE = NO
    GEODATABASE_SDE_VERSION_TYPE = Version from SDE Connection
    INTERACT = <No Spatial Filter>
    OUTPUT_FEATURES_DISPLAY = Schema and Data Features
    <SCHEMA> -> PythonCaller_3
    <OTHER> -> MeasureRemover_2
Note: XMIN und XMAX umbenennen
PythonCaller_3
    PYTHONSOURCE:
      import fmeobjects

      class RemoveSchemaAttrs(object):
          def input(self,feature):
              attr_names = feature.getAttribute('attribute{}.name')
              attr_fme_datatypes = feature.getAttribute('attribute{}.fme_data_type')
              attr_native_datatypes = feature.getAttribute('attribute{}.native_data_type')
              # attrs_to_remove = feature.getAttribute('_SCHEMA_ATTRS_TO_REMOVE').split(',')
              fme_feature_type_name = feature.getAttribute('fme_feature_type_name')
              for attr_index, attr_name in enumerate(attr_names):
                  if attr_name == 'XMAX':
                      fmeobjects.FMELogFile().logMessageString('Renaming schema attribute "%s" in schema "%s"' % (attr_name, fme_feature_type_name), fmeobjects.FME_WARN)
                      attr_names[attr_index] = 'MAXX'
                      # del attr_names[attr_index]
                      # del attr_fme_datatypes[attr_index]
                      # del attr_native_datatypes[attr_index]
                  elif attr_name == 'XMIN':
                      fmeobjects.FMELogFile().logMessageString('Renaming schema attribute "%s" in schema "%s"' % (attr_name, fme_feature_type_name), fmeobjects.FME_WARN)
                      attr_names[attr_index] = 'MINX'
              feature.removeAttribute('attribute{}.name')
              feature.removeAttribute('attribute{}.fme_data_type')
              feature.removeAttribute('attribute{}.native_data_type')
              feature.setAttribute('attribute{}.name', attr_names)
              feature.setAttribute('attribute{}.fme_data_type', attr_fme_datatypes)
              feature.setAttribute('attribute{}.native_data_type', attr_native_datatypes)

              self.pyoutput(feature)
    PYTHONSYMBOL = RemoveSchemaAttrs
    -> AttributeCreator
Note: M-Values werden entfernt (Routen)
MeasureRemover_2
    REMOVE_ALL = Yes
    -> NullAttributeMapper_2
Note: Leere Datumsfelder abfangen
NullAttributeMapper_2
    ATTRCHOICE = Selected Attributes
    ATTRLIST = $(DATEFIELDS)
    NULL_TREATMENT = Null
    OTHER_VALUE = 000000
    SOURCE_ATTR_VAL = Null
    -> PythonCaller_2
Note: Tabellenname erstellen
PythonCaller_2
    NEW_ATTRIBUTES = pg_tblname
    PYTHONSOURCE:
      import fme
      import fmeobjects

      def processFeature(feature):
          tblname_norm = feature.getAttribute("fme_feature_type")
          tblname_norm = tblname_norm.lower()

          pg_tblname = tblname_norm

          if "." in tblname_norm:
              pg_tblname = tblname_norm.split(".")[1]

          feature.setAttribute('pg_tblname', pg_tblname)
    PYTHONSYMBOL = processFeature
    -> AttributeRenamer
Note: XMIN und XMAX umbenennen
AttributeRenamer
    ATTR_TABLE:
      RENAME_SET_DEFAULT XMAX > MAXX
      RENAME_SET_DEFAULT XMIN > MINX
    -> AttributeCreator
AttributeCreator
    ATTR_TABLE = SET_TO tabellentyp = $(TABELLENTYP)
    -> AttributeFilter
Note: Tabelle oder Featureclass?
AttributeFilter
    ATTR_NAME = tabellentyp
    ATTR_VALUES = <Empty>,<Missing>,<Null>,<Unfiltered>,table,featureclass
    <EMPTY> -> Terminator
    <MISSING> -> Terminator
    <NULL> -> Terminator
    <UNFILTERED> -> Terminator
    table -> Table1 (writer POSTGRES_1)
    featureclass -> Table1 (writer POSTGIS_1)
Terminator
    MESSAGE = Translation Terminated
Note: POSTGRES-Writer
Table1 (writer POSTGRES_1)
Note: POSTGIS-Writer
Table1 (writer POSTGIS_1)
